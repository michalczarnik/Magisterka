Language="VBSCRIPT"

Sub CATMain(rad as Double)
'rad:Promień zaokrąglenia zewnętrzny prawy;2
'Image;Widok perspektywiczny;Makro12.png

Dim partDocument1 As Document
Set partDocument1 = CATIA.ActiveDocument

Dim part1 As Part
Set part1 = partDocument1.Part

Dim shapeFactory1 As Factory
Set shapeFactory1 = part1.ShapeFactory

Dim reference1 As Reference
Set reference1 = part1.CreateReferenceFromName("")

Dim constRadEdgeFillet1 As ConstRadEdgeFillet
Set constRadEdgeFillet1 = shapeFactory1.AddNewSolidEdgeFilletWithConstantRadius(reference1, catTangencyFilletEdgePropagation, 5.000000)

Dim parameters1 As Parameters
Set parameters1 = part1.Parameters

Dim length1 As Parameter
Set length1 = parameters1.Item("Part1\PartBody\EdgeFillet.4\CstEdgeRibbon.15\Radius")

length1.Value = rad

Dim bodies1 As Bodies
Set bodies1 = part1.Bodies

Dim body1 As Body
Set body1 = bodies1.Item("PartBody")

Dim shapes1 As Shapes
Set shapes1 = body1.Shapes

Dim mirror1 As Shape
Set mirror1 = shapes1.Item("Mirror.1")

Dim reference2 As Reference
Set reference2 = part1.CreateReferenceFromBRepName("TgtEdge:(GeneratedEdges;MfIE_R20GA;TgtPropagationFillet;FirstOperands:(Mirror.1);SecondOperands:();InitEdges:(REdge:(Edge:(Face:(Brp:((Brp:(Pad.1;0:(Brp:(Sketch.1;12)));Brp:(Pad.2;2);Brp:(Mirror.1;(Brp:((Brp:(Pad.1;0:(Brp:(Sketch.1;12)));Brp:(Pad.2;2)))))));None:();Cf11:());Face:(Brp:(Mirror.1;(Brp:(Pad.2;0:(Brp:(Sketch.2;8)))));None:();Cf11:());None:(Limits1:();Limits2:());Cf11:());WithTemporaryBody;WithoutBuildError;WithSelectingFeatureSupport;MFBRepVersion_CXR15)))", mirror1)

constRadEdgeFillet1.AddObjectToFillet reference2

constRadEdgeFillet1.EdgePropagation = catTangencyFilletEdgePropagation

part1.UpdateObject constRadEdgeFillet1

End Sub
