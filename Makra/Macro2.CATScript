Language="VBSCRIPT"

Sub CATMain(firstLineLength as Double, secondLineLength as Double, circle1Radius as Double, circle2Radius as Double, height as Double, depth1 as Double, depth2 as Double)
'firstLineLength:Długość podstawy;21.0
'secondLineLength:Długość górnego łączenia;2.5
'circle1Radius:Promień prawego łuku;12
'circle2Radius:Promień lewego łuku;11.6
'height:Wysokość;11.5
'depth1:Głębokość zewnętrzenej ściany;22.606
'depth2:Głębokość wewnętrznej ściany;13
'Description:Skrypt 2 - Rysowanie podstawy
'Image;Widok XY;C:\Users\micha\Desktop\Makra\Makro2XY.png
'Image;Perspektywa;C:\Users\micha\Desktop\Makra\Makro2Perspektywa.png

Dim partDocument1 As Document
Set partDocument1 = CATIA.ActiveDocument

Dim part1 As Part
Set part1 = partDocument1.Part

Dim bodies1 As Bodies
Set bodies1 = part1.Bodies

Dim body1 As Body
Set body1 = bodies1.Item("PartBody")

Dim sketches1 As Sketches
Set sketches1 = body1.Sketches

Dim originElements1 As OriginElements
Set originElements1 = part1.OriginElements

Dim reference1 As AnyObject
Set reference1 = originElements1.PlaneYZ

Dim sketch1 As Sketch
Set sketch1 = sketches1.Add(reference1)

Dim arrayOfVariantOfDouble1(8)
arrayOfVariantOfDouble1(0) = 0.000000
arrayOfVariantOfDouble1(1) = 0.000000
arrayOfVariantOfDouble1(2) = 0.000000
arrayOfVariantOfDouble1(3) = 0.000000
arrayOfVariantOfDouble1(4) = 1.000000
arrayOfVariantOfDouble1(5) = 0.000000
arrayOfVariantOfDouble1(6) = 0.000000
arrayOfVariantOfDouble1(7) = 0.000000
arrayOfVariantOfDouble1(8) = 1.000000
sketch1.SetAbsoluteAxisData arrayOfVariantOfDouble1

part1.InWorkObject = sketch1

Dim factory2D1 As Factory2D
Set factory2D1 = sketch1.OpenEdition()

Dim geometricElements1 As GeometricElements
Set geometricElements1 = sketch1.GeometricElements

Dim axis2D1 As GeometricElement
Set axis2D1 = geometricElements1.Item("AbsoluteAxis")

Dim line2D1 As CATBaseDispatch
Set line2D1 = axis2D1.GetItem("HDirection")

line2D1.ReportName = 1

Dim line2D2 As CATBaseDispatch
Set line2D2 = axis2D1.GetItem("VDirection")

line2D2.ReportName = 2

Dim point2D1 As Point2D
Set point2D1 = factory2D1.CreatePoint(-10, 0.000000)

point2D1.ReportName = 3

Dim point2D2 As Point2D
Set point2D2 = factory2D1.CreatePoint(firstLineLength-10, 0.000000)

point2D2.ReportName = 4

Dim line2D3 As Line2D
Set line2D3 = factory2D1.CreateLine(-10, 0.000000, firstLineLength-10, 0.000000)

line2D3.ReportName = 5

line2D3.StartPoint = point2D1

line2D3.EndPoint = point2D2

Dim constraints1 As Constraints
Set constraints1 = sketch1.Constraints

Dim reference2 As Reference
Set reference2 = part1.CreateReferenceFromObject(point2D1)

Dim reference3 As Reference
Set reference3 = part1.CreateReferenceFromObject(line2D1)

Dim constraint1 As Constraint
Set constraint1 = constraints1.AddBiEltCst(catCstTypeOn, reference2, reference3)

constraint1.Mode = catCstModeDrivingDimension

Dim reference4 As Reference
Set reference4 = part1.CreateReferenceFromObject(line2D3)

Dim reference5 As Reference
Set reference5 = part1.CreateReferenceFromObject(line2D1)

Dim constraint2 As Constraint
Set constraint2 = constraints1.AddBiEltCst(catCstTypeHorizontality, reference4, reference5)

constraint2.Mode = catCstModeDrivingDimension

Dim point2D3 As Point2D
Set point2D3 = factory2D1.CreatePoint(-10+firstLineLength-circle1Radius, 0.000000)

point2D3.ReportName = 6

Dim point2D4 As Point2D
Set point2D4 = factory2D1.CreatePoint(secondLineLength-0.08, height)

point2D4.ReportName = 7

Dim circle2D1 As Circle2D
Set circle2D1 = factory2D1.CreateCircle(-10+firstLineLength-circle1Radius, 0.000000, circle1Radius, 0.000000, 1.281109)

circle2D1.CenterPoint = point2D3

circle2D1.ReportName = 8

circle2D1.StartPoint = point2D2

circle2D1.EndPoint = point2D4

Dim point2D5 As Point2D
Set point2D5 = factory2D1.CreatePoint(-10+circle2Radius, 0.000000)

point2D5.ReportName = 9

Dim point2D6 As Point2D
Set point2D6 = factory2D1.CreatePoint(secondLineLength-2.42, height)

point2D6.ReportName = 10

Dim circle2D2 As Circle2D
Set circle2D2 = factory2D1.CreateCircle(-10+circle2Radius, 0.000000, circle2Radius, 1.702197, 3.141593)

circle2D2.CenterPoint = point2D5

circle2D2.ReportName = 11

circle2D2.EndPoint = point2D1

circle2D2.StartPoint = point2D6

Dim reference6 As Reference
Set reference6 = part1.CreateReferenceFromObject(point2D1)

Dim reference7 As Reference
Set reference7 = part1.CreateReferenceFromObject(line2D2)

Dim constraint3 As Constraint
Set constraint3 = constraints1.AddBiEltCst(catCstTypeDistance, reference6, reference7)

constraint3.Mode = catCstModeDrivingDimension

Dim length1 As Dimension
Set length1 = constraint3.Dimension

length1.Value = 10.000000

Dim reference8 As Reference
Set reference8 = part1.CreateReferenceFromObject(line2D2)

Dim reference9 As Reference
Set reference9 = part1.CreateReferenceFromObject(point2D2)

Dim constraint4 As Constraint
Set constraint4 = constraints1.AddBiEltCst(catCstTypeDistance, reference8, reference9)

constraint4.Mode = catCstModeDrivingDimension

Dim length2 As Dimension
Set length2 = constraint4.Dimension

length2.Value = firstLineLength-10

Dim reference10 As Reference
Set reference10 = part1.CreateReferenceFromObject(circle2D1)

Dim constraint5 As Constraint
Set constraint5 = constraints1.AddMonoEltCst(catCstTypeRadius, reference10)

constraint5.Mode = catCstModeDrivingDimension

Dim length3 As Dimension
Set length3 = constraint5.Dimension

length3.Value = circle1Radius

Dim reference11 As Reference
Set reference11 = part1.CreateReferenceFromObject(circle2D2)

Dim constraint6 As Constraint
Set constraint6 = constraints1.AddMonoEltCst(catCstTypeRadius, reference11)

constraint6.Mode = catCstModeDrivingDimension

Dim length4 As Dimension
Set length4 = constraint6.Dimension

length4.Value = circle2Radius

Dim reference12 As Reference
Set reference12 = part1.CreateReferenceFromObject(point2D5)

Dim reference13 As Reference
Set reference13 = part1.CreateReferenceFromObject(line2D3)

Dim constraint7 As Constraint
Set constraint7 = constraints1.AddBiEltCst(catCstTypeOn, reference12, reference13)

constraint7.Mode = catCstModeDrivingDimension

Dim reference14 As Reference
Set reference14 = part1.CreateReferenceFromObject(point2D3)

Dim reference15 As Reference
Set reference15 = part1.CreateReferenceFromObject(line2D3)

Dim constraint8 As Constraint
Set constraint8 = constraints1.AddBiEltCst(catCstTypeOn, reference14, reference15)

constraint8.Mode = catCstModeDrivingDimension

Dim line2D4 As Line2D
Set line2D4 = factory2D1.CreateLine(secondLineLength-2.42, height, secondLineLength-0.08, height)

line2D4.ReportName = 12

line2D4.StartPoint = point2D6

line2D4.EndPoint = point2D4

Dim reference16 As Reference
Set reference16 = part1.CreateReferenceFromObject(line2D4)

Dim reference17 As Reference
Set reference17 = part1.CreateReferenceFromObject(line2D1)

Dim constraint9 As Constraint
Set constraint9 = constraints1.AddBiEltCst(catCstTypeHorizontality, reference16, reference17)

constraint9.Mode = catCstModeDrivingDimension

Dim reference18 As Reference
Set reference18 = part1.CreateReferenceFromObject(line2D4)

Dim reference19 As Reference
Set reference19 = part1.CreateReferenceFromObject(line2D3)

Dim constraint10 As Constraint
Set constraint10 = constraints1.AddBiEltCst(catCstTypeDistance, reference18, reference19)

constraint10.Mode = catCstModeDrivingDimension

Dim length5 As Dimension
Set length5 = constraint10.Dimension

length5.Value = height

sketch1.CloseEdition 

part1.InWorkObject = sketch1

part1.UpdateObject sketch1

Dim shapeFactory1 As Factory
Set shapeFactory1 = part1.ShapeFactory

Dim pad1 As Pad
Set pad1 = shapeFactory1.AddNewPad(sketch1, 20.000000)

Dim limit1 As Limit
Set limit1 = pad1.FirstLimit

Dim length6 As Length
Set length6 = limit1.Dimension

length6.Value = 22.606000

Dim limit2 As Limit
Set limit2 = pad1.SecondLimit

Dim length7 As Length
Set length7 = limit2.Dimension

length7.Value = -13.000000

part1.UpdateObject pad1

End Sub
