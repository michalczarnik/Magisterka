Language="VBSCRIPT"

Sub CATMain()

Dim partDocument1 As Document
Set partDocument1 = CATIA.ActiveDocument

Dim part1 As Part
Set part1 = partDocument1.Part

Dim shapeFactory1 As Factory
Set shapeFactory1 = part1.ShapeFactory

Dim reference1 As Reference
Set reference1 = part1.CreateReferenceFromName("")

Dim draft1 As Draft
Set draft1 = shapeFactory1.AddNewDraft(reference1, reference1, catNoneDraftNeutralPropagationMode, reference1, 0.000000, 0.000000, 1.000000, catStandardDraftMode, 45.000000, catNoneDraftMultiselectionMode)

Dim draftDomains1 As DraftDomains
Set draftDomains1 = draft1.DraftDomains

Dim draftDomain1 As DraftDomain
Set draftDomain1 = draftDomains1.Item(1)

draftDomain1.SetPullingDirection 1.000000, 0.000000, 0.000000

Dim bodies1 As Bodies
Set bodies1 = part1.Bodies

Dim body1 As Body
Set body1 = bodies1.Item("PartBody")

Dim shapes1 As Shapes
Set shapes1 = body1.Shapes

Dim pocket1 As Shape
Set pocket1 = shapes1.Item("Pocket.1")

Dim reference2 As Reference
Set reference2 = part1.CreateReferenceFromBRepName("RSur:(Face:(Brp:(Pocket.1;1);None:();Cf11:());WithTemporaryBody;WithoutBuildError;WithSelectingFeatureSupport;MFBRepVersion_CXR15)", pocket1)

draftDomain1.AddFaceToDraft reference2

Dim reference3 As Reference
Set reference3 = part1.CreateReferenceFromBRepName("RSur:(Face:(Brp:(Pocket.1;2);None:();Cf11:());WithTemporaryBody;WithoutBuildError;WithSelectingFeatureSupport;MFBRepVersion_CXR15)", pocket1)

draftDomain1.AddFaceToDraft reference3

Dim reference4 As Reference
Set reference4 = part1.CreateReferenceFromBRepName("RSur:(Face:(Brp:(Pocket.1;0:(Brp:(Sketch.3;8)));None:();Cf11:());WithTemporaryBody;WithoutBuildError;WithSelectingFeatureSupport;MFBRepVersion_CXR15)", pocket1)

draftDomain1.NeutralElement = reference4

draftDomain1.SetPullingDirection 0.707107, 0.000000, -0.707107

Dim reference5 As Reference
Set reference5 = part1.CreateReferenceFromBRepName("FSur:(Face:(Brp:(Pocket.1;0:(Brp:(Sketch.3;8)));None:();Cf11:());WithTemporaryBody;WithoutBuildError;WithInitialFeatureSupport;MFBRepVersion_CXR15)", pocket1)

draftDomain1.PullingDirectionElement = reference5

draftDomain1.SetPullingDirection -0.707107, -0.000000, 0.707107

part1.UpdateObject draft1

End Sub
