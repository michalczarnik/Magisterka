Language="VBSCRIPT"

Sub CATMain(dlgDol as Double, przesOX as Double, wys as Double, dlgGora as Double, przesOXGora as Double, rad1 as Double, rad2 as Double, dlg as Double, przes as Double)
'dlgDol:Długość dołu;22.7
'przesOX:Przesunięcie osi X;-0.45
'wys:Wysokość; 11.5
'dlgGora:Długość góry;5.417
'przesOXGora:Przesunięcie osi X na górze;0.0645
'rad1:Promień prawy;12.2
'rad2:Promień lewy;11.8
'dlg:Długość formy;30
'przes:Przesunięcie formy;40.4
'Image;Widok perspektywiczny;Makro14Perspektywa.png
'Image;Widok XY;Makro14OX.png

Dim partDocument1 As Document
Set partDocument1 = CATIA.ActiveDocument

Dim part1 As Part
Set part1 = partDocument1.Part

Dim bodies1 As Bodies
Set bodies1 = part1.Bodies

Dim body1 As Body
Set body1 = bodies1.Item("Body.2")

Dim sketches1 As Sketches
Set sketches1 = body1.Sketches

Dim originElements1 As OriginElements
Set originElements1 = part1.OriginElements

Dim reference1 As AnyObject
Set reference1 = originElements1.PlaneZX

Dim sketch1 As Sketch
Set sketch1 = sketches1.Add(reference1)

Dim arrayOfVariantOfDouble1(8)
arrayOfVariantOfDouble1(0) = 0.000000
arrayOfVariantOfDouble1(1) = 0.000000
arrayOfVariantOfDouble1(2) = 0.000000
arrayOfVariantOfDouble1(3) = -1.000000
arrayOfVariantOfDouble1(4) = 0.000000
arrayOfVariantOfDouble1(5) = 0.000000
arrayOfVariantOfDouble1(6) = 0.000000
arrayOfVariantOfDouble1(7) = -0.000000
arrayOfVariantOfDouble1(8) = 1.000000
sketch1.SetAbsoluteAxisData arrayOfVariantOfDouble1

part1.InWorkObject = sketch1

Dim factory2D1 As Factory2D
Set factory2D1 = sketch1.OpenEdition()

Dim geometricElements1 As GeometricElements
Set geometricElements1 = sketch1.GeometricElements

Dim axis2D1 As GeometricElement
Set axis2D1 = geometricElements1.Item("AbsoluteAxis")

Dim line2D1 As CATBaseDispatch
Set line2D1 = axis2D1.GetItem("HDirection")

line2D1.ReportName = 1

Dim line2D2 As CATBaseDispatch
Set line2D2 = axis2D1.GetItem("VDirection")

line2D2.ReportName = 2

Dim point2D1 As Point2D
Set point2D1 = factory2D1.CreatePoint(-dlgDol/2+przesOX, 0.000000)

point2D1.ReportName = 3

Dim constraints1 As Constraints
Set constraints1 = sketch1.Constraints

Dim reference2 As Reference
Set reference2 = part1.CreateReferenceFromObject(point2D1)

Dim reference3 As Reference
Set reference3 = part1.CreateReferenceFromObject(line2D1)

Dim constraint1 As Constraint
Set constraint1 = constraints1.AddBiEltCst(catCstTypeOn, reference2, reference3)

constraint1.Mode = catCstModeDrivingDimension

Dim point2D2 As Point2D
Set point2D2 = factory2D1.CreatePoint(dlgDol/2+przesOX, 0.000000)

point2D2.ReportName = 4

Dim line2D3 As Line2D
Set line2D3 = factory2D1.CreateLine(-dlgDol/2+przesOX, 0.000000, dlgDol/2+przesOX, 0.000000)

line2D3.ReportName = 5

line2D3.StartPoint = point2D1

line2D3.EndPoint = point2D2

Dim reference4 As Reference
Set reference4 = part1.CreateReferenceFromObject(line2D3)

Dim reference5 As Reference
Set reference5 = part1.CreateReferenceFromObject(line2D1)

Dim constraint2 As Constraint
Set constraint2 = constraints1.AddBiEltCst(catCstTypeHorizontality, reference4, reference5)

constraint2.Mode = catCstModeDrivingDimension

Dim point2D3 As Point2D
Set point2D3 = factory2D1.CreatePoint(-1.300000, 0.000000)

point2D3.ReportName = 6

Dim point2D4 As Point2D
Set point2D4 = factory2D1.CreatePoint(dlgGora/2+przesOXGora, wys)

point2D4.ReportName = 7

Dim circle2D1 As Circle2D
Set circle2D1 = factory2D1.CreateCircle(-1.300000, 0.000000, rad1, 0.000000, 1.230402)

circle2D1.CenterPoint = point2D3

circle2D1.ReportName = 8

circle2D1.StartPoint = point2D2

circle2D1.EndPoint = point2D4

Dim point2D5 As Point2D
Set point2D5 = factory2D1.CreatePoint(0.000000, 0.000000)

point2D5.ReportName = 9

Dim point2D6 As Point2D
Set point2D6 = factory2D1.CreatePoint(-dlgGora/2+przesOXGora, wys)

point2D6.ReportName = 10

Dim circle2D2 As Circle2D
Set circle2D2 = factory2D1.CreateCircle(0.000000, 0.000000, rad2, 1.796771, 3.141593)

circle2D2.CenterPoint = point2D5

circle2D2.ReportName = 11

circle2D2.EndPoint = point2D1

circle2D2.StartPoint = point2D6

Dim point2D7 As Point2D
Set point2D7 = factory2D1.CreatePoint(-5.285312, -2.617437)

point2D7.ReportName = 12

Dim line2D4 As Line2D
Set line2D4 = factory2D1.CreateLine(dlgGora/2+przesOXGora, wys, dlgGora/2+przesOXGora, wys)

line2D4.ReportName = 13

line2D4.StartPoint = point2D4

line2D4.EndPoint = point2D6

Dim reference6 As Reference
Set reference6 = part1.CreateReferenceFromObject(line2D4)

Dim reference7 As Reference
Set reference7 = part1.CreateReferenceFromObject(line2D1)

Dim constraint3 As Constraint
Set constraint3 = constraints1.AddBiEltCst(catCstTypeHorizontality, reference6, reference7)

constraint3.Mode = catCstModeDrivingDimension

Dim reference8 As Reference
Set reference8 = part1.CreateReferenceFromObject(circle2D1)

Dim constraint4 As Constraint
Set constraint4 = constraints1.AddMonoEltCst(catCstTypeRadius, reference8)

constraint4.Mode = catCstModeDrivingDimension

Dim length1 As Dimension
Set length1 = constraint4.Dimension

length1.Value = rad1

Dim reference9 As Reference
Set reference9 = part1.CreateReferenceFromObject(circle2D2)

Dim constraint5 As Constraint
Set constraint5 = constraints1.AddMonoEltCst(catCstTypeRadius, reference9)

constraint5.Mode = catCstModeDrivingDimension

Dim length2 As Dimension
Set length2 = constraint5.Dimension

length2.Value = rad2

Dim reference10 As Reference
Set reference10 = part1.CreateReferenceFromObject(point2D3)

Dim reference11 As Reference
Set reference11 = part1.CreateReferenceFromObject(line2D3)

Dim constraint6 As Constraint
Set constraint6 = constraints1.AddBiEltCst(catCstTypeOn, reference10, reference11)

constraint6.Mode = catCstModeDrivingDimension

Dim reference12 As Reference
Set reference12 = part1.CreateReferenceFromObject(point2D5)

Dim reference13 As Reference
Set reference13 = part1.CreateReferenceFromObject(line2D3)

Dim constraint7 As Constraint
Set constraint7 = constraints1.AddBiEltCst(catCstTypeOn, reference12, reference13)

constraint7.Mode = catCstModeDrivingDimension

Dim reference14 As Reference
Set reference14 = part1.CreateReferenceFromObject(point2D3)

Dim reference15 As Reference
Set reference15 = part1.CreateReferenceFromObject(line2D2)

Dim constraint8 As Constraint
Set constraint8 = constraints1.AddBiEltCst(catCstTypeDistance, reference14, reference15)

constraint8.Mode = catCstModeDrivingDimension

Dim length3 As Dimension
Set length3 = constraint8.Dimension

length3.Value = 1.300000

Dim body2 As Body
Set body2 = bodies1.Item("PartBody")

Dim shapes1 As Shapes
Set shapes1 = body2.Shapes

Dim pad1 As Shape
Set pad1 = shapes1.Item("Pad.1")

Dim reference16 As Reference
Set reference16 = part1.CreateReferenceFromBRepName("FSur:(Face:(Brp:((Brp:(Pad.1;0:(Brp:(Sketch.1;12)));Brp:(Pad.2;2);Brp:(Mirror.1;(Brp:((Brp:(Pad.1;0:(Brp:(Sketch.1;12)));Brp:(Pad.2;2)))))));None:();Cf11:());WithPermanentBody;WithoutBuildError;WithInitialFeatureSupport;MonoFond;MFBRepVersion_CXR15)", pad1)

Dim geometricElements2 As GeometricElements
Set geometricElements2 = factory2D1.CreateIntersections(reference16)

Dim geometry2D1 As GeometricElement
Set geometry2D1 = geometricElements2.Item("Mark.1")

geometry2D1.Construction = True

Dim reference17 As Reference
Set reference17 = part1.CreateReferenceFromObject(line2D4)

Dim reference18 As Reference
Set reference18 = part1.CreateReferenceFromObject(geometry2D1)

Dim constraint9 As Constraint
Set constraint9 = constraints1.AddBiEltCst(catCstTypeOn, reference17, reference18)

constraint9.Mode = catCstModeDrivingDimension

Dim reference19 As Reference
Set reference19 = part1.CreateReferenceFromObject(point2D5)

Dim reference20 As Reference
Set reference20 = part1.CreateReferenceFromObject(line2D2)

Dim constraint10 As Constraint
Set constraint10 = constraints1.AddBiEltCst(catCstTypeOn, reference19, reference20)

constraint10.Mode = catCstModeDrivingDimension

sketch1.CloseEdition 

part1.InWorkObject = sketch1

part1.UpdateObject sketch1

Dim shapeFactory1 As Factory
Set shapeFactory1 = part1.ShapeFactory

Dim pad2 As Pad
Set pad2 = shapeFactory1.AddNewPad(sketch1, 20.000000)

pad2.DirectionOrientation = catInverseOrientation

Dim limit1 As Limit
Set limit1 = pad2.FirstLimit

Dim length4 As Length
Set length4 = limit1.Dimension

length4.Value = dlg+przes

Dim limit2 As Limit
Set limit2 = pad2.SecondLimit

Dim length5 As Length
Set length5 = limit2.Dimension

length5.Value = -przes

part1.UpdateObject pad2

End Sub
